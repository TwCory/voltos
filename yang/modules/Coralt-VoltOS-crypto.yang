module Coralt-VoltOS-crypto {

    grouping config-crypto-grouping {
        container crypto {
            
        }
    }

    grouping config-key-grouping {

    }

    grouping interface-crypto-grouping {
        container crypto {

        }
    }
}
