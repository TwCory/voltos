module Coralt-VoltOS-zerotier-oper {
    yang-version 1.1;
    namespace "";
    prefix voltos-zerotier-oper;

    typedef zerotier-event-type {
        type enumeration {
            enum up;
            enum offline;
            enum down;
            enum error-identity-collision;
            enum trace;
            enum user-message;
            enum remote-trace;
        }
    }
}
