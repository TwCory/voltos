module Coralt-VoltOS-ip {
    
    import ietf-inet-types {
        prefix inet;
    }

    grouping config-ip-grouping {
        container access-list {
            description
                "Named IP Access-List Configuration";
        }
        leaf accounting-list;
        leaf accounting-threshold;
        leaf accounting-transits;
        leaf address-pool {
            description
                "Specify IP Address Pooling Method";
            type enumeration {
                enum dhcp-pool;
                enum dhcp-proxy-client;
                enum local;
            }
        }
        container admission {
            description
                "Network Admission Control (NAC) Configuration";
        }
        leaf alias;
        container arp {
            description
                "IP ARP Global Configuration";
        }
        container as-path {
            description
                "BGP AS_PATH Attribute Filter Configuration";
        }
        container auth-proxy;
        container bgp-community {
            description
                "Specify Format for BGP Communities";
            leaf new-format {
                description
                    "Select AA:NN Format for BGP Communities";
                type boolean;
            }
        }
        container bootp {
            description
                "Configure IP BOOTP Services";
            leaf server {
                description
                    "Enable BOOTP Server";
                type boolean;
            }
        }
        container cache-invalidate-delay;
        leaf classless {
            description
                "Follow Classless IP Routing/Forwarding Rules";
            type boolean;
            default "true";
        }
        container cofp {
            description
                "Coralt Optimized Forwarding Plane (COFP) for IP";
        }
        leaf community-list;
        container dccp;
        container ddns;
        leaf default-gateway {
            description
                "Specify Default Gateway Address (If Not Routing IP)";
            type inet:ipv4-address;
        }
        leaf default-network;
        container device;
        container dhcp {
            description
                "Configure IP DHCP Server and Relay Parameters";
        }
        container dhcp-client {
            description
                "Configure IP DHCP Client Operational Parameters";
        }
        container dhcp-relay {
            description
                "Configure IP DHCP Relay Agent";
        }
        container dhcp-server {
            description
                "Configure IP DHCP Server Parameters";
        }
        container diameter {
            leaf source-interface;
        }
        container dns {
            description
                "Configure DNS Server for a Zone";
        }
        container domain {
            description
                "IP Domain Name System (DNS) Resolver";
            leaf list;
            leaf lookup;
            leaf multicast;
            leaf name;
            leaf round-robin;
            leaf timeout;
        }
        leaf domain-list;
        leaf domain-lookup;
        leaf domain-name;

        leaf explicit-path;
        leaf extcommunity-list;

        container finger {
            description
                "Finger Protocol Server Configuration";
        }
        container flow;
        container flow-aggregation;
        container flow-cache;
        container flow-capture;
        container flow-export;
        container flow-top-talkers;
        container forward-protocol {
            description
                "Control Forwarding of Physical/Directed Network Broadcasts";
            leaf nd {
                type boolean;
                default "true";
            }
            leaf sdns {
                type boolean;
            }
            container spanning-tree {
                leaf any-local-broadcast {
                    type boolean;
                }
            }
            container turbo-flood {
                leaf udp-checksum {
                    type boolean;
                }
            }
            container udp;
        }
        container ftp {
            leaf passive;
            leaf password;
            leaf source-interface;
            leaf username;
        }
        container gdp;
        leaf gratuitous-arps;
        leaf host;
        leaf host-list;
        leaf host-routing {
            description
                "Enable Host-Based Routing (Proxy ARP and ICMP Redirect)";
            type boolean;
        }
        container hostname {
            description
                "Configure Hostname Options";
            leaf strict {
                description
                    "Allow Only Hostnames Compliant with RFC 1123";
                type boolean;
                default "false";
            }
        }
        leaf hp-host {
            type boolean;
        }
        container http;
        container icmp;
        leaf ident {
            type boolean;
        }
        container igmp;
        container inspect;
        container kerberos {
            leaf source-interface;
        }
        container ldap {
            leaf source-interface;
        }
        container local {
            description
                "Specify IP Local Options";
            leaf policy;
            leaf pool;
        }
        container mfib;
        leaf mobile;
        leaf mpf;
        leaf mrm;
        leaf mroute;
        container msdp;
        container multicast;
        leaf multicast-routing {
            type boolean;
        }
        container mux;
        container name-server;
        container nat;
        container nbar;
        container options {
            leaf drop {
                type boolean;
            }
        }
        container ospf {
            description
                "Configure for OSPF";
            leaf name-lookup {
                description
                    "Display OSPF Router IDs as DNS Names";
                type boolean;
            }
        }
        container pgm;
        container pim;
        leaf policy-list;
        leaf port-map;
        leaf prefix-list;
        container pxf;
        container quic;
        container radius {
            leaf source-interface;
        }
        container rcmd;
        leaf reflexive-list;
        leaf route;
        leaf routing {
            description
                "Enable/Disable IP Routing";
            type boolean;
            default "true";
        }
        container routing-conf {
            container protocol {
                container purge {
                    leaf interface {
                        type boolean;
                    }
                }
            }
        }
        container rsvp;
        leaf sap;
        leaf scp;
        container sctp;
        leaf sdee;
        leaf sdr;
        leaf security;
        container sla;
        container slb;
        leaf source-route {
            type boolean;
        }
        leaf source-track;
        container spd;
        container ssh;
        leaf sticky-arp {
            type boolean;
        }
        leaf subnet-zero {
            description
                "Allow for Subnet-Zero IP Networks";
            type boolean;
        }
        container tacacs {
            leaf source-interface;
        }
        container tcp {
            leaf chunk-size;
            leaf ecn;
            leaf keepalive;
            leaf mss;
            leaf path-mtu-discovery;
            leaf queuemax;
            leaf selective-ack;
            leaf synwait-time;
            leaf timestamp;
            leaf window-size;
        }
        container telnet {
            leaf source-interface;
        }
        container tftp {
            leaf source-interface;
        }
        leaf trigger-authentication;
        container udp;
        container udp-lite;
        leaf udptn;
        leaf urd;
        container url-filter;
        container verify;
        list vrf {
            description
                "Configure an IP VPN Routing/Forwarding Instance";
        }
        container wccp;
    }

    grouping interface-ip-grouping {
        container access-group;
        container accounting;
        container address;
        container admission;
        container arp {
            container inspection {
                container limit;
                leaf trust;
            }
        }
        leaf audit;
        leaf auth-proxy;
        leaf authentication;
        leaf broadcast-address {
            type inet:ipv4-address;
        }
        leaf clear-dont-fragment {
            type boolean;
        }
        leaf cofp;
        leaf dampening-change;
        leaf dccp;
        leaf dhcp;
        leaf directed-broadcast {
            type boolean;
        }
        container dvmrp;

        leaf header-compression;
        leaf hello-interval;
        leaf helper-address {
            type inet:ipv4-address;
        }
        leaf hold-time;

        leaf ips;

        leaf local-proxy-arp {
            type boolean;
        }

        leaf mask-reply {
            type boolean;
        }
        leaf mroute-cache {
            type boolean;
        }
        leaf mtu {
            type uint16 {
                range "68..18000";
            }
            default "1500";
        }
        leaf mux;
        leaf nat;
        leaf nbar;
        leaf network-broadcast {
            type boolean;
        }
        leaf next-hop-self;
        leaf nhrp;
        leaf ospf;
        leaf pgm;
        leaf pim;
        leaf policy;
        leaf proxy-arp {
            type boolean;
        }
        leaf quic;
        leaf rarp-server {
            type boolean;
        }
        leaf redirects {
            type boolean;
        }
        leaf rip;
        leaf route-cache;
        leaf router;

        leaf sctp;
        leaf split-horizon;
        leaf sticky-arp {
            type boolean;
        }
        leaf summary-address;

        container tcp {
            leaf adjust-mss;
            leaf header-compression;
        }
        leaf traffic-export;
        leaf trigger-authentication;
        leaf ttl {
            type uint8;
        }
        leaf udp;
        leaf udp-lite;
        leaf unnumbered {
            type boolean;
        }
        leaf unreachables {
            type boolean;
        }
        leaf verify;
        leaf virtual-reassembly;
        container vrf {
            container forwarding;
            leaf receive;
            leaf sitemap;
        }
        leaf wccp;
    }

    augment "/voltos:main/voltos:ip" {
        uses config-ip-grouping;
    }
}
