module Coralt-VoltOS-main {
    
    import Coralt-VoltOS-types {
        prefix voltos-types;
    }

    container main {
        container aaa {
            description
                "Authentication, Authorization and Accounting";
        }
        container aal2-profile {
            description
                "ATM Adaptation Layer 2 (AAL2) Profile Configuration";
        }
        container access-list {
            description
                "Add an Access Control List Entry";
        }
        container alarm-contact {
            description
                "Alarm Contact Configuration Commands";
        }
        leaf alias {
            description
                "Create a Command Alias";
        }
        container alps {
            description
                "Airline Product Set (ALPS) Configuration";
        }
        container appfw {
            description
                "Configure the Application Firewall Policy";
        }
        container appletalk {
            description
                "Global AppleTalk Configuration Commands";
        }
        container aqm-register-fnf {
            description
                "Export Audio/Video Stats to a Flow Record";
        }
        container archive {
            description
                "Archive the System Configuration";
        }
        leaf arp {
            description
                "Set a Static ARP Cache Entry";
        }
        container async-bootp {
            description
                "Modify System BOOTP Parameters";
        }
        container authentication {
            description
                "Configure Authentication Options";
        }
        container auto {
            description
                "Configure Automation";
        }
        container avb {
            description
                "Audio-Video Bridging (AVB) Configuration";
        }
        container avc {
            description
                "Application Visibility and Control (AVC) Configuration";
        }
        container backhaul-session-manager {
            description
                "Configure the Backhaul Session Manager";
        }
        container banner {
            description
                "Define a Login Banner";
        }
        container bba-group {
            description
                "Configure Broadband Aggregation (BBA) Group";
        }
        container beep {
            description
                "Configure Blocks Extensible Exchange Protocol (BEEP)";
        }
        container bfd {
            description
                "BFD Configuration Commands";
        }
        container bfd-template {
            description
                "BFD-Template Configuration";
        }
        container boot {
            description
                "Modify System Boot Parameters";
        }
        container bridge {
            description
                "Bridge Global Configuration Commands";
        }
        container bridge-domain {
            description
                "Bridge-Domain Global Configuration Commands";
        }
        container bridge-group {
            description
                "Bridge-Group Global Configuration";
        }
        container bstun {
            description
                "Block Serial Tunnel (BSTUN) Configuration Commands";
        }
        container buffers {
            description
                "Modify System Buffer Pool Parameters";
        }
        container bulkstat {
            description
                "Bulkstat Application Configuration";
        }
        leaf busy-message {
            description
                "Display Message When Connection to Host Fails";
        }
        container call {
            description
                "Call Configuration Commands";
        }
        container call-home {
            description
                "Enter Call-Home Configuration Mode";
        }
        leaf captive-portal-bypass {
            description
                "Enable Captive Portal Bypass for Apple Devices";
        }
        container card;
        container carrier-id;
        container cdma;
        container cdp {
            description
                "CDP Configuration Commands";
        }
        container cfg-mode;
        container chat-script {
            description
                "Define a Modem Chat Script";
        }
        container cisp {
            description
                "Configure CISP Parameters";
        }
        container class-map {
            description
                "Configure a QoS Class Map";
        }
        container clns {
            description
                "Global CLNS Configuration Commands";
        }
        container clock {
            description
                "Configure System Clock";
        }
        container cofp;
        container connect {
            description
                "Cross-Connect Multiple Interfaces";
        }
        container control-plane {
            description
                "Configure Control Plane Services";
        }
        container controller {
            description
                "Interface Controller Configuration";
        }
        container crypto {
            description
                "Crypto/Encryption Engine Configuration";
        }
        container csdb {
            description
                "Common Session Database (CSDB) Configuration";
        }
        container cwmp {
            description
                "CPE WAN Management Protocol (CWMP) Module Configuration";
        }
        container cws {
            description
                "Cloud Web Security (CWS) Configuration";
        }
        container decnet {
            description
                "Global DECnet Configuration Commands";
        }
        leaf default-value;
        leaf define;
        container device-sensor;
        container device-tracking;
        leaf dialer;
        leaf dialer-list;
        container diameter {
            description
                "Diameter Server Configuration Commands";
        }
        container dlsw {
            description
                "Data-Link Switching (DLSW) Global Configuration";
        }
        container dnsix-dmdp;
        container dnsix-nat;
        leaf domain;
        container dot1x {
            description
                "IEEE 802.1X Global Configuration Commands";
        }
        leaf downward-compatible-config {
            description
                "Generate a Backwards-Compatible System Configuration";
        }
        container dspu {
            description
                "Down-Stream Physical Unit (DSPU) Configuration";
        }
        container eap;
        container enable {
            description
                "Modify Enable Password Parameters";
        }
        container endpoint-tracker {
            description
                "Endpoint Tracker Configuration Commands";
        }
        container eou {
            description
                "EAPoUDP Global Configuration";
        }
        container epm;
        container ethernet {
            description
                "Global Ethernet Configuration";
        }
        container event;
        container exception {
            description
                "Exception Handling Options";
        }
        container fabric;
        container facility-alarm;
        container fallback;
        container fhrp {
            description
                "Configure First-Hop Redundancy Protocol (FHRP) Parameters";
        }
        container file;
        container flow {
            description
                "Global Flow Configuration Commands";
        }
        leaf flow-sampler-map;
        leaf format;
        container frame-relay {
            description
                "Global Frame-Relay Configuration";
        }
        container global-address-family {
            description
                "Global Address Family Template Configuration";
        }
        container gvrp;
        leaf help;
        leaf hostname {
            description
                "Set the System's Network Name";
        }
        container http {
            description
                "HTTP Client Configuration Parameters";
        }
        container hw-module;
        container hw-programmable;
        container ida-client;
        container identity;
        container interface {
            description
                "Select an Interface to Configure";
        }
        container iox {
            description
                "Configure IOx Services";
        }
        container ip {
            description
                "Global IP Configuration Commands";
        }
        container ipc {
            description
                "Configure the IPC Subsystem";
        }
        container iphc-profile {
            description
                "Configure an IP Header Compression Profile";
        }
        container ipv6 {
            description
                "Global IPv6 Configuration Commands";
        }
        container ipx {
            description
                "Global IPX Configuration Commands";
        }
        container isdn;
        container isis;
        container ixi;
        container kerberos;
        container key {
            description
                "System Key Management";
        }
        leaf keymap;
        container kron;
        container l2 {
            description
                "Layer 2 Configuration";
        }
        container l2tp {
            description
                "Layer 2 Tunneling Protocol (L2TP) Configuration";
        }
        leaf l2tp-class {
            description
                "L2TP Class Configuration";
        }
        container l2vpn {
            description
                "Layer 2 VPN Configuration Commands";
        }
        container l3vpn {
            description
                "Layer 3 VPN Configuration Commands";
        }
        container lacp;
        container lat {
            description
                "DEC Local Area Transport (LAT) Global Configuration";
        }
        container ldap {
            description
                "LDAP Server Configuration Commands";
        }
        container line {
            description
                "Configure a Terminal Line";
        }
        container lldp {
            description
                "LLDP Configuration Commands";
        }
        leaf locaddr-priority-list;
        container location {
            description
                "Global Location Configuration Commands";
        }
        container logging {
            description
                "Configure Logging Parameters";
        }
        container login {
            description
                "Enable Secure Login Checking";
        }
        container login-string;
        container mab {
            description
                "MAC Authentication Bypass Configuration";
        }
        container mac-address-table {
            description
                "Configure the MAC Address Table";
        }
        leaf map-class;
        leaf map-list;
        container mediatrace;
        container memory {
            description
                "Configure Memory Management";
        }
        container memory-size {
            description
                "Adjust Memory Size Using Percentage";
        }
        container metadata {
            description
                "Metadata Application Configuration";
        }
        container microcode;
        container mka;
        container mls;
        container modemcap;
        container monitor {
            description
                "VoltOS Event Monitoring Configuration";
        }
        container mop;
        container mpls {
            description
                "Global MPLS Configuration Commands";
        }
        container multilink {
            description
                "PPP Multilink Global Configuration";
        }
        container nat64;
        container netbios;
        container netconf;
        container network-clock;
        container ntp;
        container object-group {
            description
                "Configure an Object Group";
        }
        container onep;
        leaf parameter-map;
        container parser;
        container password;
        container performance;
        container pfr {
            description
                "Performance Routing (PfR) Configuration";
        }
        leaf pfr-map;
        leaf policy;
        leaf policy-map;
        container ppp;
        leaf pppoe;
        container privilege;
        container process;
        container process-max-time;
        leaf profile;
        leaf pseudowire-class {
            description
                "Pseudowire-Class Configuration";
        }
        container ptp;
        container qos {
            description
                "Global QoS Configuration Commands";
        }
        container radius {
            description
                "RADIUS Server Configuration Commands";
        }
        container radius-server {
            description
                "Modify RADIUS Query Parameters";
        }
        container rbe;
        container redundancy {
            description
                "Enter Redundancy Configuration Mode";
        }
        leaf regex;
        leaf remote-management;
        leaf rlogin;
        leaf rmon;
        leaf route-map;
        container route-tag;
        container router {
            description
                "Enable a Routing Protocol Process";
        }
        container rsrb;
        container sampler;
        leaf sap-priority-list;
        container scheduler {
            description
                "VoltOS Scheduler Configuration Parameters";
        }
        container scripting;
        container sdm;
        container secure;
        container security;
        container service {
            description
                "Modify the Usage of Network and System Services";
        }
        container service-chain;
        container service-class;
        container service-discovery;
        container service-insertion;
        container service-instance;
        leaf service-list;
        container service-module;
        container service-routing;
        container setup {
            description
                "Express Setup Utility Configuration Parameters";
        }
        container snmp {
            description
                "Modify SNMP Non-Engine Parameters";
        }
        container snmp-server {
            description
                "Modify SNMP Server Engine Parameters";
        }
        container sntp {
            description
                "Simple NTP (SNTP) Configuration";
        }
        container spanning-tree {
            description
                "Spanning Tree Protocol Subsystem Configuration";
        }
        container spe;
        container standby {
            description
                "Hot Standby Router Protocol (HSRP) Configuration";
        }
        leaf subscriber;
        leaf table-map;
        container tacacs {
            description
                "TACACS+ Server Configuration Commands";
        }
        container tacacs-server {
            description
                "Modify TACACS+ Query Parameters";
        }
        container tarp;
        container tdm;
        container tech-support;
        leaf template;
        leaf terminal-queue;
        container tftp-server {
            description
                "Provide TFTP Service for Netload Requests";
        }
        leaf time-range;
        container tn3270;
        container tod-clock {
            description
                "Configure the Time-of-Day (ToD) Clock";
        }
        leaf track;
        leaf transceiver;
        leaf translate;
        leaf transport-map {
            description
                "Configure a Transport Map";
        }
        leaf trunk;
        leaf ttycap;
        leaf udld;
        leaf upgrade;
        leaf user-group;
        leaf username {
            description
                "Establish User Name Authentication";
        }
        leaf vc-group;
        leaf version {
            description
                "VoltOS Version";
        }
        leaf virtual-profile;
        leaf virtual-service;
        leaf virtual-template;
        container vlan {
            description
                "Global VLAN Configuration";
        }
        leaf vofm;
        leaf voice;
        leaf voice-class;
        leaf voice-port;
        leaf vpdn;
        leaf vpdn-group;
        leaf vpdn-template;
        container vrf;
        container vrrs;
        container vty-async;
        container vxlan {
            description
                "VxLAN Configuration Commands";
        }
        container vxml;
        container waas;
        container webvpn;
        container wlccp;
        container wsma {
            description
                "Web Services Management Agent (WAAS) Configuration";
        }
        container x25 {
            description
                "Global X.25 Configuration Commands";
        }
        container x28 {
            description
                "X.28 Global Configuration";
        }
        container x29;
        container x3;
        container xconnect;
        container xml;
        container xot {
            description
                "X.25 over TCP (XoT) Configuration Commands";
        }
        container xsm;
        container zone {
            description
                "Zone-Based Firewall Configuration Commands";
        }
        container zone-pair {
            description
                "Zone Pair Configuration Commands";
        }
    }
}
