module Coralt-VoltOS-bridge {
    yang-version 1.1;
    namespace "";
    prefix voltos-bridge;

    grouping config-bridge-grouping {

    }

    grouping config-bridge-group-grouping {
        
    }
}
