module Coralt-VoltOS-acl {
    yang-version 1.1;
    namespace "";
    prefix voltos-acl;

    grouping config-access-list-grouping {

    }

    grouping config-ip-access-list-grouping {
        
    }

    grouping config-ipv6-access-list-grouping {

    }
}
