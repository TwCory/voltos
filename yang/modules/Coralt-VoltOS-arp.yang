module Coralt-VoltOS-arp {
    yang-version 1.1;
    namespace "";
    prefix voltos-arp;

    import ietf-inet-type {
        prefix inet;
    }

    import Coralt-VoltOS-arp-types {
        prefix voltos-arp-types;
    }

    grouping config-arp-grouping {

    }

    grouping interface-arp-grouping {
        
    }
}
