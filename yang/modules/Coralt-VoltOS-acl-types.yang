module Coralt-VoltOS-acl-types {
    yang-version 1.1;
    namespace "";
    prefix voltos-acl-types;

    typedef acl-type {
        type enumeration {
            enum ipv4-extended;
            enum ipv4-standard;
        }
    }
}
