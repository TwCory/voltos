module Coralt-VoltOS-l2tp {
    yang-version 1.1;
    namespace "";
    prefix voltos-l2tp;

    grouping config-l2tp-grouping {
        container l2tp {

        }
    }

    grouping config-l2tp-class-grouping {
        container l2tp-class {
            
        }
    }
}
