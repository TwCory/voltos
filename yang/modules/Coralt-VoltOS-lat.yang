module Coralt-VoltOS-lat {
    yang-version 1.1;
    namespace "";
    prefix voltos-lat;

    grouping config-lat-grouping {
        container lat {

        }
    }

    grouping interface-lat-grouping {
        container lat {
            
        }
    }
}
