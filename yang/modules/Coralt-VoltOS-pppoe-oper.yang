module Coralt-VoltOS-pppoe-oper {
    yang-version 1.1;
    namespace "";
    prefix voltos-pppoe-oper;

    typedef pppoe-role-type {
        type enumeration {
            enum client {
                value 1;
            }
            enum server {
                value 2;
            }
        }
    }
}
