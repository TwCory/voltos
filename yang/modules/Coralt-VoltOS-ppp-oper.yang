module Coralt-VoltOS-ppp-oper {
    yang-version 1.1;
    namespace "";
    prefix voltos-ppp-oper;

    typedef ppp-auth-type {
        type enumeration {
            enum none {
                value 0;
            }
            enum chap {
                value 1;
            }
            enum pap {
                value 2;
            }
            enum mschap {
                value 3;
            }
            enum mschapv2 {
                value 4;
            }
            enum eap {
                value 5;
            }
        }
    }
}
