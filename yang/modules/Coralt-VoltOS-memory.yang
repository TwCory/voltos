module Coralt-VoltOS-memory {
    yang-version 1.1;
    namespace "";
    prefix voltos-memory;

    grouping config-memory-grouping {

    }

    grouping config-memory-size-grouping {
        
    }
}
