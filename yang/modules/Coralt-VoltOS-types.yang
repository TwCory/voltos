module Coralt-VoltOS-types {
    yang-version 1.1;
    prefix voltos-types;

    typedef appletalk-address;

    typedef dccp-port;
    typedef domain-name;

    typedef hostname;

    typedef ip-address;
    typedef ip-port;
    typedef ip-prefix;
    typedef ip-protocol;

    typedef ipv4-address;
    typedef ipv4-prefix;

    typedef ipv6-address;
    typedef ipv6-prefix;

    typedef mac-address;
    typedef mac-prefix;

    typedef nsap-address;

    typedef sctp-port;

    typedef tcp-port;

    typedef udp-port;
    typedef url;

    typedef vlan-id;



}
