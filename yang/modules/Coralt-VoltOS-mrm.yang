module Coralt-VoltOS-mrm {
    yang-version 1.1;
    namespace "";
    prefix voltos-mrm;

    grouping config-mrm-grouping {

    }

    grouping config-ip-mrm-grouping {

    }

    grouping config-ipv6-mrm-grouping {
        
    }
}
