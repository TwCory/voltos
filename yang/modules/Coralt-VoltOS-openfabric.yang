module Coralt-VoltOS-openfabric {
    yang-version 1.1;
    namespace "";
    prefix voltos-openfabric;

    grouping router-openfabric-grouping {

    }

    grouping ipv6-router-openfabric-grouping {

    }
}
