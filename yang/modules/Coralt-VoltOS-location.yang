module Coralt-VoltOS-location {
    yang-version 1.1;
    namespace "";
    prefix voltos-location;

    grouping config-location-grouping {
        container location {
            
        }
    }
}
