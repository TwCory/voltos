module Coralt-VoltOS-interfaces {

    grouping interface-common-grouping {
        leaf aaa;
        leaf access-session;
        leaf appletalk;
        leaf arp;
        leaf backup;
        leaf bandwidth;
        leaf bfd;
        leaf cdp;
        leaf cemoudp;
        leaf clns;
        leaf clock;
        leaf crypto;
        leaf dampening;
        leaf decnet;
        leaf default;
        leaf delay;
        leaf description;
        leaf dlsw;
        leaf domain;
        leaf duplex;
        leaf encapsulation;
        leaf ethernet;
        leaf export-name;
        leaf fair-queue;
        leaf flow-control;
        leaf history;
        leaf hold-queue;
        leaf ip;
        leaf ipv6;
        leaf ipx;
        leaf isis;
        leaf keepalive;
        leaf lldp;
        leaf load-interval;
        leaf logging;
        leaf mac-address;
        leaf max-reserved-bandwidth;
        leaf mdix;
        leaf media-type;
        leaf mop;
        leaf mpls;
        leaf mtu;
        leaf nat64;
        leaf ospfv3;
        leaf peer;
        leaf pm-path;
        leaf priority-queue;
        leaf punt-control;
        leaf qos;
        leaf rcv-queue;
        leaf redundancy;
        leaf service-insertion;
        leaf shutdown;
        leaf source;
        leaf spanning-tree;
        leaf speed;
        leaf srlg;
        leaf standby;
        leaf storm-control;
        leaf subscriber;
        leaf switchport;
        leaf trust;
        leaf uplink;
        leaf vrf;
    }
}
