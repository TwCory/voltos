module Coralt-VoltOS-appletalk {
    yang-version 1.1;
    namespace "";
    prefix voltos-appletalk;

    grouping config-appletalk-grouping {

    }

    grouping interface-appletalk-grouping {
        
    }
}
