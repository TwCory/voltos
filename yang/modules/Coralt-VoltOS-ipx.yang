module Coralt-VoltOS-ipx {
    yang-version 1.1;
    namespace "";
    prefix voltos-ipx;

    grouping config-ipx-grouping {
        container ipx {

        }
    }

    grouping interface-ipx-grouping {
        container ipx {
            
        }
    }
}
