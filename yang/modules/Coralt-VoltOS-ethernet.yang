module Coralt-VoltOS-ethernet {

    grouping config-ethernet-grouping {
        container ethernet {

        }
    }

    grouping interface-ethernet-grouping {
        container ethernet {
            
        }
    }
}
