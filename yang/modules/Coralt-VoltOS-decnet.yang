module Coralt-VoltOS-decnet {
    yang-version 1.1;
    namespace "";
    prefix voltos-decnet;

    grouping config-decnet-grouping {

    }

    grouping interface-decnet-grouping {
        
    }
}
