module Coralt-VoltOS-nhrp {
    yang-version 1.1;
    namespace "";
    prefix voltos-nhrp;

    grouping interface-ip-nhrp-grouping {

    }

    grouping interface-ipv6-nhrp-grouping {
        
    }
}
