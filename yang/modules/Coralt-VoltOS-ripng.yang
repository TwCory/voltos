module Coralt-VoltOS-ripng {
    yang-version 1.1;
    namespace "";
    prefix voltos-ripng;

    grouping config-ipv6-rip-grouping {
        
    }

    grouping ipv6-router-rip-grouping {

    }

    grouping interface-ipv6-rip-grouping {

    }
}
